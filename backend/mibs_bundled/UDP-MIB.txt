UDP-MIB DEFINITIONS ::= BEGIN

IMPORTS
    MODULE-IDENTITY, OBJECT-TYPE, Counter32, Integer32, IpAddress,
    mib-2
        FROM SNMPv2-SMI
    MODULE-COMPLIANCE, OBJECT-GROUP
        FROM SNMPv2-CONF;

udpMIB MODULE-IDENTITY
    LAST-UPDATED "200205090000Z"
    ORGANIZATION "IETF"
    CONTACT-INFO "IETF SNMPv2 Working Group"
    DESCRIPTION  "The MIB module for managing UDP implementations."
    REVISION     "200205090000Z"
    DESCRIPTION  "Initial version."
    ::= { mib-2 50 }

udp OBJECT IDENTIFIER ::= { mib-2 7 }

udpInDatagrams OBJECT-TYPE
    SYNTAX     Counter32
    MAX-ACCESS read-only
    STATUS     current
    DESCRIPTION "Total UDP datagrams delivered to users."
    ::= { udp 1 }

udpNoPorts OBJECT-TYPE
    SYNTAX     Counter32
    MAX-ACCESS read-only
    STATUS     current
    DESCRIPTION "Datagrams for which no app was at destination port."
    ::= { udp 2 }

udpInErrors OBJECT-TYPE
    SYNTAX     Counter32
    MAX-ACCESS read-only
    STATUS     current
    DESCRIPTION "Datagrams unable to be delivered for other reasons."
    ::= { udp 3 }

udpOutDatagrams OBJECT-TYPE
    SYNTAX     Counter32
    MAX-ACCESS read-only
    STATUS     current
    DESCRIPTION "Total UDP datagrams sent."
    ::= { udp 4 }

udpTable OBJECT-TYPE
    SYNTAX     SEQUENCE OF UdpEntry
    MAX-ACCESS not-accessible
    STATUS     deprecated
    DESCRIPTION "Table of UDP listener information."
    ::= { udp 5 }

UdpEntry ::= SEQUENCE {
    udpLocalAddress IpAddress,
    udpLocalPort    Integer32
}

udpEntry OBJECT-TYPE
    SYNTAX     UdpEntry
    MAX-ACCESS not-accessible
    STATUS     deprecated
    DESCRIPTION "UDP listener entry."
    INDEX { udpLocalAddress, udpLocalPort }
    ::= { udpTable 1 }

udpLocalAddress OBJECT-TYPE
    SYNTAX     IpAddress
    MAX-ACCESS read-only
    STATUS     deprecated
    DESCRIPTION "Local IP address for this UDP listener."
    ::= { udpEntry 1 }

udpLocalPort OBJECT-TYPE
    SYNTAX     Integer32 (0..65535)
    MAX-ACCESS read-only
    STATUS     deprecated
    DESCRIPTION "Local port for this UDP listener."
    ::= { udpEntry 2 }

END
