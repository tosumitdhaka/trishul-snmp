HOST-RESOURCES-MIB DEFINITIONS ::= BEGIN

IMPORTS
    MODULE-IDENTITY, OBJECT-TYPE, Integer32, Counter32, Gauge32,
    TimeTicks, mib-2
        FROM SNMPv2-SMI
    DisplayString, TruthValue, DateAndTime
        FROM SNMPv2-TC
    MODULE-COMPLIANCE, OBJECT-GROUP
        FROM SNMPv2-CONF;

hostResourcesMibModule MODULE-IDENTITY
    LAST-UPDATED "200003060000Z"
    ORGANIZATION "IETF"
    CONTACT-INFO "IETF Host Resources MIB Working Group"
    DESCRIPTION  "The MIB module for host resources: CPU, memory, storage, processes."
    REVISION     "200003060000Z"
    DESCRIPTION  "Initial version, published as RFC 2790."
    ::= { mib-2 25 }

host OBJECT IDENTIFIER ::= { mib-2 25 }

hrSystem        OBJECT IDENTIFIER ::= { host 1 }
hrStorage       OBJECT IDENTIFIER ::= { host 2 }
hrDevice        OBJECT IDENTIFIER ::= { host 3 }
hrSWRun         OBJECT IDENTIFIER ::= { host 4 }
hrSWRunPerf     OBJECT IDENTIFIER ::= { host 5 }
hrSWInstalled   OBJECT IDENTIFIER ::= { host 6 }

hrSystemUptime OBJECT-TYPE
    SYNTAX     TimeTicks
    MAX-ACCESS read-only
    STATUS     current
    DESCRIPTION "System uptime in hundredths of a second."
    ::= { hrSystem 1 }

hrSystemDate OBJECT-TYPE
    SYNTAX     DateAndTime
    MAX-ACCESS read-write
    STATUS     current
    DESCRIPTION "Host's notion of the local date and time."
    ::= { hrSystem 2 }

hrSystemNumUsers OBJECT-TYPE
    SYNTAX     Gauge32
    MAX-ACCESS read-only
    STATUS     current
    DESCRIPTION "Number of user sessions currently active."
    ::= { hrSystem 5 }

hrSystemProcesses OBJECT-TYPE
    SYNTAX     Gauge32
    MAX-ACCESS read-only
    STATUS     current
    DESCRIPTION "Number of process contexts currently loaded or running."
    ::= { hrSystem 6 }

hrMemorySize OBJECT-TYPE
    SYNTAX     Integer32
    UNITS      "KBytes"
    MAX-ACCESS read-only
    STATUS     current
    DESCRIPTION "Total RAM in KBytes."
    ::= { hrStorage 2 }

hrStorageTable OBJECT-TYPE
    SYNTAX     SEQUENCE OF HrStorageEntry
    MAX-ACCESS not-accessible
    STATUS     current
    DESCRIPTION "Table of storage areas on the host."
    ::= { hrStorage 3 }

HrStorageEntry ::= SEQUENCE {
    hrStorageIndex       Integer32,
    hrStorageType        OBJECT IDENTIFIER,
    hrStorageDescr       DisplayString,
    hrStorageAllocationUnits Integer32,
    hrStorageSize        Integer32,
    hrStorageUsed        Integer32,
    hrStorageAllocationFailures Counter32
}

hrStorageEntry OBJECT-TYPE
    SYNTAX     HrStorageEntry
    MAX-ACCESS not-accessible
    STATUS     current
    DESCRIPTION "Storage area entry."
    INDEX { hrStorageIndex }
    ::= { hrStorageTable 1 }

hrStorageIndex OBJECT-TYPE
    SYNTAX     Integer32 (1..2147483647)
    MAX-ACCESS read-only
    STATUS     current
    DESCRIPTION "Index for this storage entry."
    ::= { hrStorageEntry 1 }

hrStorageDescr OBJECT-TYPE
    SYNTAX     DisplayString
    MAX-ACCESS read-only
    STATUS     current
    DESCRIPTION "Description of this storage area."
    ::= { hrStorageEntry 3 }

hrStorageAllocationUnits OBJECT-TYPE
    SYNTAX     Integer32 (1..2147483647)
    UNITS      "Bytes"
    MAX-ACCESS read-only
    STATUS     current
    DESCRIPTION "Size in bytes of each allocation unit."
    ::= { hrStorageEntry 4 }

hrStorageSize OBJECT-TYPE
    SYNTAX     Integer32
    MAX-ACCESS read-write
    STATUS     current
    DESCRIPTION "Size of the storage in allocation units."
    ::= { hrStorageEntry 5 }

hrStorageUsed OBJECT-TYPE
    SYNTAX     Integer32
    MAX-ACCESS read-only
    STATUS     current
    DESCRIPTION "Amount of storage used in allocation units."
    ::= { hrStorageEntry 6 }

hrProcessorTable OBJECT-TYPE
    SYNTAX     SEQUENCE OF HrProcessorEntry
    MAX-ACCESS not-accessible
    STATUS     current
    DESCRIPTION "Table of processors on the host."
    ::= { hrDevice 3 }

HrProcessorEntry ::= SEQUENCE {
    hrProcessorFrwID    OBJECT IDENTIFIER,
    hrProcessorLoad     Integer32
}

hrProcessorEntry OBJECT-TYPE
    SYNTAX     HrProcessorEntry
    MAX-ACCESS not-accessible
    STATUS     current
    DESCRIPTION "Processor entry."
    INDEX { hrDeviceIndex }
    ::= { hrProcessorTable 1 }

hrProcessorLoad OBJECT-TYPE
    SYNTAX     Integer32 (0..100)
    UNITS      "percent"
    MAX-ACCESS read-only
    STATUS     current
    DESCRIPTION "Average CPU load over last minute as percentage."
    ::= { hrProcessorEntry 2 }

END
