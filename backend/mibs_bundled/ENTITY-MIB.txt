ENTITY-MIB DEFINITIONS ::= BEGIN

IMPORTS
    MODULE-IDENTITY, OBJECT-TYPE, Integer32, mib-2
        FROM SNMPv2-SMI
    TruthValue, DisplayString, PhysAddress
        FROM SNMPv2-TC
    MODULE-COMPLIANCE, OBJECT-GROUP
        FROM SNMPv2-CONF;

entityMIB MODULE-IDENTITY
    LAST-UPDATED "200508180000Z"
    ORGANIZATION "IETF"
    CONTACT-INFO "IETF Entity MIB Working Group"
    DESCRIPTION  "MIB module for representing multiple logical entities on a single agent."
    REVISION     "200508180000Z"
    DESCRIPTION  "Third version published as RFC 4133."
    ::= { mib-2 47 }

entityMIBObjects    OBJECT IDENTIFIER ::= { entityMIB 1 }
entPhysical         OBJECT IDENTIFIER ::= { entityMIBObjects 1 }
entLogical          OBJECT IDENTIFIER ::= { entityMIBObjects 2 }
entLPMappings       OBJECT IDENTIFIER ::= { entityMIBObjects 3 }
entAliasMappings    OBJECT IDENTIFIER ::= { entityMIBObjects 4 }
entPhysicalContains OBJECT IDENTIFIER ::= { entityMIBObjects 5 }

entPhysicalTable OBJECT-TYPE
    SYNTAX      SEQUENCE OF EntPhysicalEntry
    MAX-ACCESS  not-accessible
    STATUS      current
    DESCRIPTION "Table of physical components."
    ::= { entPhysical 1 }

EntPhysicalEntry ::= SEQUENCE {
    entPhysicalIndex       Integer32,
    entPhysicalDescr       DisplayString,
    entPhysicalVendorType  OBJECT IDENTIFIER,
    entPhysicalContainedIn Integer32,
    entPhysicalClass       INTEGER,
    entPhysicalParentRelPos Integer32,
    entPhysicalName        DisplayString,
    entPhysicalHardwareRev DisplayString,
    entPhysicalFirmwareRev DisplayString,
    entPhysicalSoftwareRev DisplayString,
    entPhysicalSerialNum   DisplayString,
    entPhysicalMfgName     DisplayString,
    entPhysicalModelName   DisplayString,
    entPhysicalAlias       DisplayString,
    entPhysicalAssetID     DisplayString,
    entPhysicalIsFRU       TruthValue
}

entPhysicalEntry OBJECT-TYPE
    SYNTAX      EntPhysicalEntry
    MAX-ACCESS  not-accessible
    STATUS      current
    DESCRIPTION "Physical component entry."
    INDEX { entPhysicalIndex }
    ::= { entPhysicalTable 1 }

entPhysicalIndex OBJECT-TYPE
    SYNTAX      Integer32 (1..2147483647)
    MAX-ACCESS  read-only
    STATUS      current
    DESCRIPTION "Index for this physical component."
    ::= { entPhysicalEntry 1 }

entPhysicalDescr OBJECT-TYPE
    SYNTAX      DisplayString
    MAX-ACCESS  read-only
    STATUS      current
    DESCRIPTION "Textual description of physical component."
    ::= { entPhysicalEntry 2 }

entPhysicalClass OBJECT-TYPE
    SYNTAX      INTEGER {
                    other(1), unknown(2), chassis(3), backplane(4),
                    container(5), powerSupply(6), fan(7), sensor(8),
                    module(9), port(10), stack(11), cpu(12)
                }
    MAX-ACCESS  read-only
    STATUS      current
    DESCRIPTION "General hardware type of this component."
    ::= { entPhysicalEntry 5 }

entPhysicalName OBJECT-TYPE
    SYNTAX      DisplayString
    MAX-ACCESS  read-only
    STATUS      current
    DESCRIPTION "Textual name assigned by local device to this component."
    ::= { entPhysicalEntry 7 }

entPhysicalSerialNum OBJECT-TYPE
    SYNTAX      DisplayString (SIZE(0..32))
    MAX-ACCESS  read-write
    STATUS      current
    DESCRIPTION "Vendor-specific serial number of this component."
    ::= { entPhysicalEntry 11 }

entPhysicalIsFRU OBJECT-TYPE
    SYNTAX      TruthValue
    MAX-ACCESS  read-only
    STATUS      current
    DESCRIPTION "Whether this component is a Field Replaceable Unit."
    ::= { entPhysicalEntry 16 }

END
