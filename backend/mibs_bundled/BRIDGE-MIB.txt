BRIDGE-MIB DEFINITIONS ::= BEGIN

IMPORTS
    MODULE-IDENTITY, OBJECT-TYPE, Counter32, Integer32,
    TimeTicks, mib-2
        FROM SNMPv2-SMI
    TEXTUAL-CONVENTION, TruthValue
        FROM SNMPv2-TC
    MODULE-COMPLIANCE, OBJECT-GROUP
        FROM SNMPv2-CONF;

dot1dBridge MODULE-IDENTITY
    LAST-UPDATED "200509190000Z"
    ORGANIZATION "IETF Bridge MIB Working Group"
    CONTACT-INFO "Work in progress"
    DESCRIPTION  "The Bridge MIB module for managing devices that support IEEE 802.1D."
    REVISION     "200509190000Z"
    DESCRIPTION  "Third version published as RFC 4188."
    ::= { mib-2 17 }

dot1dBase      OBJECT IDENTIFIER ::= { dot1dBridge 1 }
dot1dStp       OBJECT IDENTIFIER ::= { dot1dBridge 2 }
dot1dSr        OBJECT IDENTIFIER ::= { dot1dBridge 3 }
dot1dTp        OBJECT IDENTIFIER ::= { dot1dBridge 4 }
dot1dStatic    OBJECT IDENTIFIER ::= { dot1dBridge 5 }

dot1dBaseBridgeAddress OBJECT-TYPE
    SYNTAX     OCTET STRING (SIZE(6))
    MAX-ACCESS read-only
    STATUS     current
    DESCRIPTION "MAC address used by this bridge."
    ::= { dot1dBase 1 }

dot1dBaseNumPorts OBJECT-TYPE
    SYNTAX     Integer32
    MAX-ACCESS read-only
    STATUS     current
    DESCRIPTION "Number of ports controlled by this bridging entity."
    ::= { dot1dBase 2 }

dot1dBaseType OBJECT-TYPE
    SYNTAX     INTEGER { unknown(1), transparent-only(2),
                         sourceroute-only(3), srt(4) }
    MAX-ACCESS read-only
    STATUS     current
    DESCRIPTION "Type of bridging this entity can perform."
    ::= { dot1dBase 3 }

dot1dStpProtocolSpecification OBJECT-TYPE
    SYNTAX     INTEGER { unknown(1), decLan100BridgeSTP(2), ieee8021d(3) }
    MAX-ACCESS read-only
    STATUS     current
    DESCRIPTION "Version of Spanning Tree Protocol being run."
    ::= { dot1dStp 1 }

dot1dStpPriority OBJECT-TYPE
    SYNTAX     Integer32 (0..65535)
    MAX-ACCESS read-write
    STATUS     current
    DESCRIPTION "Bridge priority used in STP root election."
    ::= { dot1dStp 2 }

dot1dStpTimeSinceTopologyChange OBJECT-TYPE
    SYNTAX     TimeTicks
    MAX-ACCESS read-only
    STATUS     current
    DESCRIPTION "Time since last topology change."
    ::= { dot1dStp 3 }

dot1dStpTopChanges OBJECT-TYPE
    SYNTAX     Counter32
    MAX-ACCESS read-only
    STATUS     current
    DESCRIPTION "Total number of topology changes."
    ::= { dot1dStp 4 }

dot1dStpDesignatedRoot OBJECT-TYPE
    SYNTAX     OCTET STRING (SIZE(8))
    MAX-ACCESS read-only
    STATUS     current
    DESCRIPTION "Bridge identifier of the root of the spanning tree."
    ::= { dot1dStp 5 }

dot1dTpLearnedEntryDiscards OBJECT-TYPE
    SYNTAX     Counter32
    MAX-ACCESS read-only
    STATUS     current
    DESCRIPTION "Forwarding database entries discarded due to lack of space."
    ::= { dot1dTp 1 }

dot1dTpAgingTime OBJECT-TYPE
    SYNTAX     Integer32 (10..1000000)
    MAX-ACCESS read-write
    STATUS     current
    DESCRIPTION "Timeout for dynamic entries in the forwarding database."
    ::= { dot1dTp 2 }

END
