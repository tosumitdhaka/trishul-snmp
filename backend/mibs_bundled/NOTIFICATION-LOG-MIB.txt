NOTIFICATION-LOG-MIB DEFINITIONS ::= BEGIN

IMPORTS
    MODULE-IDENTITY, OBJECT-TYPE, Integer32, Counter32,
    TimeTicks, mib-2
        FROM SNMPv2-SMI
    RowStatus, StorageType, DisplayString, DateAndTime,
    TruthValue
        FROM SNMPv2-TC
    MODULE-COMPLIANCE, OBJECT-GROUP
        FROM SNMPv2-CONF
    SnmpAdminString
        FROM SNMP-FRAMEWORK-MIB;

notificationLogMIB MODULE-IDENTITY
    LAST-UPDATED "200011270000Z"
    ORGANIZATION "IETF Distributed Management Working Group"
    CONTACT-INFO "IETF Distributed Management Working Group"
    DESCRIPTION  "The MIB module for logging SNMP Notifications."
    REVISION     "200011270000Z"
    DESCRIPTION  "Initial version, RFC 3014."
    ::= { mib-2 92 }

nlmMIBObjects   OBJECT IDENTIFIER ::= { notificationLogMIB 1 }
nlmConfig       OBJECT IDENTIFIER ::= { nlmMIBObjects 1 }
nlmStats        OBJECT IDENTIFIER ::= { nlmMIBObjects 2 }
nlmLog          OBJECT IDENTIFIER ::= { nlmMIBObjects 3 }

nlmConfigGlobalEntryLimit OBJECT-TYPE
    SYNTAX      Unsigned32
    MAX-ACCESS  read-write
    STATUS      current
    DESCRIPTION "Global max number of notification log entries."
    DEFVAL { 0 }
    ::= { nlmConfig 1 }

nlmConfigGlobalAgeOut OBJECT-TYPE
    SYNTAX      Unsigned32
    UNITS       "minutes"
    MAX-ACCESS  read-write
    STATUS      current
    DESCRIPTION "Minutes before an entry is aged out (0=never)."
    DEFVAL { 1440 }
    ::= { nlmConfig 2 }

nlmStatsGlobalNotificationsLogged OBJECT-TYPE
    SYNTAX      Counter32
    MAX-ACCESS  read-only
    STATUS      current
    DESCRIPTION "Total notifications that have been logged."
    ::= { nlmStats 1 }

nlmStatsGlobalNotificationsBumped OBJECT-TYPE
    SYNTAX      Counter32
    MAX-ACCESS  read-only
    STATUS      current
    DESCRIPTION "Notifications dropped due to log size limit."
    ::= { nlmStats 2 }

nlmLogTable OBJECT-TYPE
    SYNTAX      SEQUENCE OF NlmLogEntry
    MAX-ACCESS  not-accessible
    STATUS      current
    DESCRIPTION "Table of logged notifications."
    ::= { nlmLog 1 }

NlmLogEntry ::= SEQUENCE {
    nlmLogIndex         Unsigned32,
    nlmLogTime          TimeTicks,
    nlmLogDateAndTime   DateAndTime,
    nlmLogEngineID      OCTET STRING,
    nlmLogEngineTAddress OCTET STRING,
    nlmLogContextName   SnmpAdminString,
    nlmLogNotificationID OBJECT IDENTIFIER
}

nlmLogEntry OBJECT-TYPE
    SYNTAX      NlmLogEntry
    MAX-ACCESS  not-accessible
    STATUS      current
    DESCRIPTION "A log entry for a notification."
    INDEX { nlmLogName, nlmLogIndex }
    ::= { nlmLogTable 1 }

nlmLogTime OBJECT-TYPE
    SYNTAX      TimeTicks
    MAX-ACCESS  read-only
    STATUS      current
    DESCRIPTION "sysUpTime when notification was logged."
    ::= { nlmLogEntry 2 }

nlmLogNotificationID OBJECT-TYPE
    SYNTAX      OBJECT IDENTIFIER
    MAX-ACCESS  read-only
    STATUS      current
    DESCRIPTION "OID of the notification."
    ::= { nlmLogEntry 7 }

END
