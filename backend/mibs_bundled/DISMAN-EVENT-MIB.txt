DISMAN-EVENT-MIB DEFINITIONS ::= BEGIN

IMPORTS
    MODULE-IDENTITY, OBJECT-TYPE, Integer32, Counter32,
    NOTIFICATION-TYPE, TimeTicks, mib-2
        FROM SNMPv2-SMI
    RowStatus, StorageType, TruthValue, DisplayString,
    DateAndTime
        FROM SNMPv2-TC
    MODULE-COMPLIANCE, OBJECT-GROUP, NOTIFICATION-GROUP
        FROM SNMPv2-CONF;

dismanEventMIB MODULE-IDENTITY
    LAST-UPDATED "200010151000Z"
    ORGANIZATION "IETF Distributed Management Working Group"
    CONTACT-INFO "IETF Distributed Management Working Group"
    DESCRIPTION  "The MIB module for defining event triggers and actions."
    REVISION     "200010151000Z"
    DESCRIPTION  "Initial version, as RFC 2981."
    ::= { mib-2 88 }

dismanEventMIBObjects     OBJECT IDENTIFIER ::= { dismanEventMIB 1 }
mteResource               OBJECT IDENTIFIER ::= { dismanEventMIBObjects 1 }
mteTrigger                OBJECT IDENTIFIER ::= { dismanEventMIBObjects 2 }
mteEvent                  OBJECT IDENTIFIER ::= { dismanEventMIBObjects 4 }

mteResourceSampleMinimum OBJECT-TYPE
    SYNTAX      Integer32 (1..2147483647)
    UNITS       "seconds"
    MAX-ACCESS  read-write
    STATUS      current
    DESCRIPTION "Minimum mteTriggerFrequency allowed."
    DEFVAL { 1 }
    ::= { mteResource 1 }

mteResourceSampleInstanceMaximum OBJECT-TYPE
    SYNTAX      Gauge32
    MAX-ACCESS  read-write
    STATUS      current
    DESCRIPTION "Maximum instances for sampling trigger objects."
    DEFVAL { 0 }
    ::= { mteResource 2 }

mteTriggerTable OBJECT-TYPE
    SYNTAX      SEQUENCE OF MteTriggerEntry
    MAX-ACCESS  not-accessible
    STATUS      current
    DESCRIPTION "Table of trigger entries."
    ::= { mteTrigger 2 }

MteTriggerEntry ::= SEQUENCE {
    mteOwner              DisplayString,
    mteTriggerName        DisplayString,
    mteTriggerComment     DisplayString,
    mteTriggerTest        BITS,
    mteTriggerSampleType  INTEGER,
    mteTriggerValueID     OBJECT IDENTIFIER,
    mteTriggerEnabled     TruthValue,
    mteTriggerEntryStatus RowStatus
}

mteTriggerEntry OBJECT-TYPE
    SYNTAX      MteTriggerEntry
    MAX-ACCESS  not-accessible
    STATUS      current
    DESCRIPTION "A trigger entry."
    INDEX { mteOwner, mteTriggerName }
    ::= { mteTriggerTable 1 }

mteOwner OBJECT-TYPE
    SYNTAX      DisplayString (SIZE(0..32))
    MAX-ACCESS  not-accessible
    STATUS      current
    DESCRIPTION "Owner of this trigger."
    ::= { mteTriggerEntry 1 }

mteTriggerName OBJECT-TYPE
    SYNTAX      DisplayString (SIZE(1..32))
    MAX-ACCESS  not-accessible
    STATUS      current
    DESCRIPTION "Name of this trigger."
    ::= { mteTriggerEntry 2 }

mteTriggerEnabled OBJECT-TYPE
    SYNTAX      TruthValue
    MAX-ACCESS  read-create
    STATUS      current
    DESCRIPTION "Whether this trigger is active."
    ::= { mteTriggerEntry 6 }

mteTriggerEntryStatus OBJECT-TYPE
    SYNTAX      RowStatus
    MAX-ACCESS  read-create
    STATUS      current
    DESCRIPTION "Status of this conceptual row."
    ::= { mteTriggerEntry 12 }

END
